# -*- coding: utf-8 -*-
# Parametric first-pass quadcopter redesign for FreeCAD.
# Units: mm. Hardware dimensions are explicit placeholders until measured.
import os, json, math, traceback
import FreeCAD as App
import Part
import Mesh
from FreeCAD import Vector

OUT = os.path.abspath("build/modular-redesign")
os.makedirs(OUT, exist_ok=True)
DOC_NAME = "ModularQuietQuadcopter"
doc = App.newDocument(DOC_NAME)

# ---------------- Editable design parameters (mm) ----------------
BODY_X, BODY_Y = 72.0, 60.0
TRAY_HEIGHT, FLOOR = 18.0, 3.0
LID_THICKNESS = 5.0
SCREW_X, SCREW_Y = 25.0, 20.0
CLEARANCE_HOLE = 3.4       # M3 clearance; use M3 screws + suitable inserts/nuts
SCREW_HEAD_DIA, SCREW_HEAD_DEPTH = 6.2, 1.7
ARM_WIDTH, ARM_THICKNESS = 9.0, 5.0
MOTOR_CENTER_LOCAL = 42.0
MOTOR_PAD = 16.0
MOTOR_HOLE_SPACING = 9.0   # placeholder: measure the actual motor pattern
MOTOR_HOLE_DIA = 2.2       # placeholder for small motor screws
GUARD_OUTER_R, GUARD_INNER_R = 23.5, 20.5
GUARD_Z0, GUARD_HEIGHT = 13.0, 13.0
PROP_RADIUS = 19.0
PROP_HUB_R, PROP_HUB_H = 4.6, 3.2
PROP_SHAFT_BORE = 2.0      # placeholder: measure the motor shaft
CAMERA_ANGLE_DEG = 15.0    # fixed down-tilt concept
PRINT_BED_X = PRINT_BED_Y = 200.0

def box(x, y, z, dx, dy, dz):
    return Part.makeBox(dx, dy, dz, Vector(x, y, z))

def cylinder(r, h, x, y, z):
    return Part.makeCylinder(r, h, Vector(x, y, z))

def must_be_valid(shape, label):
    if shape.isNull():
        raise RuntimeError(label + ": null shape")
    if not shape.isValid():
        raise RuntimeError(label + ": invalid shape")
    return shape

def make_lower_tray():
    outer = box(-BODY_X/2, -BODY_Y/2, 0, BODY_X, BODY_Y, TRAY_HEIGHT)
    # A flat 3 mm floor and open cavity; screw counterbores are only on the underside.
    cavity = box(-BODY_X/2+3.0, -BODY_Y/2+3.0, FLOOR,
                 BODY_X-6.0, BODY_Y-6.0, TRAY_HEIGHT-FLOOR+0.2)
    tray = outer.cut(cavity)
    for sx in (-1, 1):
        for sy in (-1, 1):
            x, y = sx*SCREW_X, sy*SCREW_Y
            tray = tray.cut(cylinder(CLEARANCE_HOLE/2, TRAY_HEIGHT+0.2, x, y, -0.1))
            tray = tray.cut(cylinder(SCREW_HEAD_DIA/2, SCREW_HEAD_DEPTH,
                                     x, y, -0.01))
    return must_be_valid(tray, "LowerTray")

def make_upper_lid():
    lid = box(-BODY_X/2, -BODY_Y/2, TRAY_HEIGHT,
              BODY_X, BODY_Y, LID_THICKNESS)
    # Underside bosses give the M3 screws a deeper clamping region.
    for sx in (-1, 1):
        for sy in (-1, 1):
            x, y = sx*SCREW_X, sy*SCREW_Y
            lid = lid.fuse(cylinder(4.5, 5.0, x, y, TRAY_HEIGHT-5.0))
    for sx in (-1, 1):
        for sy in (-1, 1):
            lid = lid.cut(cylinder(CLEARANCE_HOLE/2, LID_THICKNESS+5.2,
                                   sx*SCREW_X, sy*SCREW_Y, TRAY_HEIGHT-5.1))
    return must_be_valid(lid.removeSplitter(), "UpperLid")

def make_arm_local():
    # One independent arm, in local coordinates. The guard is structurally fused to it.
    root = box(-8.0, -9.0, 13.0, 17.0, 18.0, 5.0)
    beam = box(0.0, -ARM_WIDTH/2, 13.0, MOTOR_CENTER_LOCAL,
               ARM_WIDTH, ARM_THICKNESS)
    motor_pad = box(MOTOR_CENTER_LOCAL-MOTOR_PAD/2, -MOTOR_PAD/2, 13.0,
                    MOTOR_PAD, MOTOR_PAD, 4.0)
    guard_outer = cylinder(GUARD_OUTER_R, GUARD_HEIGHT,
                           MOTOR_CENTER_LOCAL, 0, GUARD_Z0)
    guard_inner = cylinder(GUARD_INNER_R, GUARD_HEIGHT+0.2,
                           MOTOR_CENTER_LOCAL, 0, GUARD_Z0-0.1)
    guard = guard_outer.cut(guard_inner)
    arm = root.fuse(beam).fuse(motor_pad).fuse(guard)
    # One shared M3 clamp screw through the lower shell, arm and upper lid.
    arm = arm.cut(cylinder(CLEARANCE_HOLE/2, 5.2, 0, 0, 12.9))
    # Motor mounting pattern: provisional, must be matched to the selected motor.
    hs = MOTOR_HOLE_SPACING/2
    for x in (-hs, hs):
        for y in (-hs, hs):
            arm = arm.cut(cylinder(MOTOR_HOLE_DIA/2, 4.2,
                                   MOTOR_CENTER_LOCAL+x, y, 12.9))
    return must_be_valid(arm.removeSplitter(), "ArmWithGuard")

def section_wire(radius, chord, twist_deg, serration):
    # NACA-0012-like section; chordwise points are twisted about the radial axis.
    pts = []
    n = 18
    def point(xc, sign):
        yt = 5.0*0.12*chord*(0.2969*math.sqrt(max(xc, 1e-5))
             - 0.1260*xc - 0.3516*xc*xc + 0.2843*xc**3 - 0.1015*xc**4)
        yy = (0.5-xc)*chord + serration*(1.0-xc)
        zz = sign*yt
        a = math.radians(twist_deg)
        y2 = yy*math.cos(a) - zz*math.sin(a)
        z2 = yy*math.sin(a) + zz*math.cos(a)
        return Vector(radius, y2, z2)
    # Upper surface leading-to-trailing, then lower surface trailing-to-leading.
    for i in range(n+1):
        x = 0.5*(1.0-math.cos(math.pi*i/n))
        pts.append(point(x, 1.0))
    for i in range(n, -1, -1):
        x = 0.5*(1.0-math.cos(math.pi*i/n))
        pts.append(point(x, -1.0))
    pts.append(pts[0])
    return Part.makePolygon(pts)

def make_quiet_propeller():
    # Concept only: two blades, reduced chord/twist toward the tip, rounded tip station,
    # and a shallow spanwise serration on the trailing edge. Not flight validated.
    stations = [4.0, 5.5, 7.0, 8.5, 10.0, 11.5, 13.0, 14.5, 16.0, 17.5, 18.5, PROP_RADIUS]
    def interp(r, arr):
        keys = [(4.0, 8.0), (7.0, 9.5), (10.0, 9.0), (13.0, 7.2),
                (16.0, 5.2), (18.5, 2.6), (PROP_RADIUS, 1.2)]
        for i in range(len(keys)-1):
            if keys[i][0] <= r <= keys[i+1][0]:
                x0,y0=keys[i]; x1,y1=keys[i+1]
                return y0+(y1-y0)*(r-x0)/(x1-x0)
        return keys[-1][1]
    wires=[]
    for i,r in enumerate(stations):
        chord = interp(r, None)
        twist = max(3.0, 25.0 - (r-4.0)*1.25)
        # Triangular wave: modest serrations (about 0.7 mm amplitude).
        phase = ((r-4.0) % 3.0)/3.0
        tri = 1.0 - abs(2.0*phase-1.0)
        serr = 0.65*(2.0*tri-1.0)
        wires.append(section_wire(r, chord, twist, serr))
    try:
        blade = Part.makeLoft(wires, True, False)
        must_be_valid(blade, "PropellerBladeLoft")
        # The second blade is a 180-degree copy around the shaft axis.
        blade2 = blade.copy()
        blade2.rotate(Vector(0,0,0), Vector(0,0,1), 180)
        hub = cylinder(PROP_HUB_R, PROP_HUB_H, 0, 0, -PROP_HUB_H/2)
        prop = hub.fuse(blade).fuse(blade2)
        prop = prop.cut(cylinder(PROP_SHAFT_BORE/2, PROP_HUB_H+2, 0, 0,
                                 -PROP_HUB_H/2-1))
        prop = prop.removeSplitter()
        return must_be_valid(prop, "QuietPropeller")
    except Exception as exc:
        print("Airfoil loft failed; using robust low-profile serrated prototype:", str(exc))
        # Fallback planform with a shallow serrated trailing edge; still a prototype.
        outline = [Vector(3.5, 3.5, -0.9), Vector(7, 4.5, -0.9),
                   Vector(11, 4.0, -0.9), Vector(15, 2.8, -0.9),
                   Vector(18, 1.4, -0.9), Vector(PROP_RADIUS, 0.6, -0.9)]
        for r in [18.5,17.0,15.5,14.0,12.5,11.0,9.5,8.0,6.5,5.0,3.5]:
            amp = 0.65 if int(r*2)%2 else -0.65
            chord = interp(r, None)
            outline.append(Vector(r, -max(0.5,chord/2)+amp, -0.9))
        outline.append(outline[0])
        face = Part.Face(Part.Wire(Part.makePolygon(outline).Edges))
        b1 = face.extrude(Vector(0,0,1.8))
        b2 = b1.copy()
        b2.rotate(Vector(0,0,0), Vector(0,0,1), 180)
        prop = cylinder(PROP_HUB_R, PROP_HUB_H, 0, 0, -PROP_HUB_H/2).fuse(b1).fuse(b2)
        prop = prop.cut(cylinder(PROP_SHAFT_BORE/2, PROP_HUB_H+2, 0, 0,
                                 -PROP_HUB_H/2-1))
        return must_be_valid(prop.removeSplitter(), "FallbackQuietPropeller")

def make_camera_mount_local():
    # Flat plate tilted 15 degrees down, with two provisional mounting holes.
    plate = box(-14.0, -8.0, -1.5, 28.0, 16.0, 3.0)
    for x in (-7.0, 7.0):
        plate = plate.cut(cylinder(1.6, 4.0, x, 0, -2.0))
    center = Vector(0,0,0)
    plate.rotate(center, Vector(1,0,0), CAMERA_ANGLE_DEG)
    return must_be_valid(plate, "CameraMount")

def add_feature(name, label, shape):
    obj = doc.addObject("Part::Feature", name)
    obj.Label = label
    obj.Shape = shape
    return obj

def export_local(shape, basename):
    # Export local-coordinate parts for easy placement in a slicer.
    tmp = doc.addObject("Part::Feature", "ExportTemp")
    tmp.Shape = shape
    doc.recompute()
    Part.export([tmp], os.path.join(OUT, basename + ".step"))
    Mesh.export([tmp], os.path.join(OUT, basename + ".stl"))
    doc.removeObject(tmp.Name)
    doc.recompute()

try:
    lower = make_lower_tray()
    lid = make_upper_lid()
    arm_local = make_arm_local()
    prop_local = make_quiet_propeller()
    camera_local = make_camera_mount_local()

    assembly = []
    lower_obj = add_feature("LowerTray", "Lower electronics tray - flat floor", lower)
    lid_obj = add_feature("UpperLid", "Upper lid - four M3 clamp points", lid)
    assembly.extend([lower_obj, lid_obj])

    part_report = []
    local_parts = [("lower_tray", lower), ("upper_lid", lid),
                   ("arm_guard", arm_local), ("quiet_propeller", prop_local),
                   ("camera_mount", camera_local)]
    # Four independent arms; each carries its own guard ring.
    arm_specs = []
    for sx in (-1, 1):
        for sy in (-1, 1):
            root = Vector(sx*SCREW_X, sy*SCREW_Y, 0)
            motor = Vector(sx*52.0, sy*52.0, 0)
            dx,dy = motor.x-root.x, motor.y-root.y
            length = math.sqrt(dx*dx+dy*dy)
            angle = math.degrees(math.atan2(dy,dx))
            transformed = arm_local.copy()
            transformed.rotate(Vector(0,0,0), Vector(0,0,1), angle)
            transformed.translate(root)
            arm_name = "Arm_%s_%s" % ("L" if sx<0 else "R", "F" if sy<0 else "B")
            arm_obj = add_feature(arm_name, "Independent arm + integrated rotor guard", transformed)
            assembly.append(arm_obj)
            arm_specs.append((arm_name, arm_local))
            # One matched prop at each motor centre. Local files remain centred at origin.
            p = prop_local.copy()
            p.translate(Vector(sx*52.0, sy*52.0, 20.5))
            prop_obj = add_feature("Prop_%s_%s" % ("L" if sx<0 else "R", "F" if sy<0 else "B"),
                                   "Quiet propeller concept - unvalidated", p)
            assembly.append(prop_obj)

    cam = camera_local.copy()
    cam.translate(Vector(0, -36.0, 8.0))
    cam_obj = add_feature("CameraMount", "Fixed camera mount - 15 deg downward concept", cam)
    assembly.append(cam_obj)

    # Save each printable component in its own local coordinate frame.
    export_local(lower, "lower_tray")
    export_local(lid, "upper_lid")
    export_local(arm_local, "arm_with_integrated_guard")
    export_local(prop_local, "quiet_propeller_prototype")
    export_local(camera_local, "fixed_camera_mount")

    # A native FreeCAD assembly and a STEP assembly are also included.
    doc.recompute()
    assembly_step = os.path.join(OUT, "quadcopter_modular_assembly.step")
    Part.export(assembly, assembly_step)
    fcstd = os.path.join(OUT, "quadcopter_modular_assembly.FCStd")
    doc.recompute()
    doc.saveAs(fcstd)

    for name, shape in local_parts:
        bb = shape.BoundBox
        ex = [round(bb.XLength,3), round(bb.YLength,3), round(bb.ZLength,3)]
        part_report.append({
            "part": name, "valid": bool(shape.isValid()), "closed": bool(shape.isClosed()),
            "extents_mm": ex, "within_200x200_bed_by_xy_bounds": bool(bb.XLength <= PRINT_BED_X and bb.YLength <= PRINT_BED_Y)
        })
    # Arms share the same local geometry; list each physical part separately.
    for name, shape in arm_specs:
        bb = shape.BoundBox
        part_report.append({"part": name, "valid": bool(shape.isValid()),
            "extents_mm": [round(bb.XLength,3),round(bb.YLength,3),round(bb.ZLength,3)],
            "within_200x200_bed_by_xy_bounds": bool(bb.XLength <= PRINT_BED_X and bb.YLength <= PRINT_BED_Y)})
    report = {
        "status": "conceptual_parametric_first_pass",
        "units": "mm",
        "source_branch_modified": False,
        "parameters": {
            "body_xy": [BODY_X, BODY_Y], "tray_height": TRAY_HEIGHT, "floor_thickness": FLOOR,
            "lid_thickness": LID_THICKNESS, "fasteners": "4 x M3 underside screws, one per arm",
            "motor_mount_hole_spacing_mm": MOTOR_HOLE_SPACING, "motor_mount_hole_diameter_mm": MOTOR_HOLE_DIA,
            "propeller_radius_mm": PROP_RADIUS, "guard_outer_diameter_mm": 2*GUARD_OUTER_R,
            "guard_inner_diameter_mm": 2*GUARD_INNER_R, "camera_down_angle_deg": CAMERA_ANGLE_DEG,
            "print_bed_mm": [PRINT_BED_X, PRINT_BED_Y]
        },
        "parts": part_report,
        "research_note": "Trailing-edge serrations and reduced tip loading are literature-informed concepts, not a measured acoustic result. Do not run printed propellers at flight RPM without balancing, containment, thrust and vibration tests.",
        "fit_limitations": [
            "Motor hole pattern and shaft bore are provisional; measure the actual motor before printing.",
            "Battery, flight controller, ESC, wiring and camera dimensions are not supplied; internal fit is not yet verified.",
            "The arm root clamp uses four M3 screws; thread engagement/inserts and structural load capacity require verification.",
            "The design is not flight-ready and has not undergone structural, vibration, thrust, thermal or acoustic validation."
        ]
    }
    with open(os.path.join(OUT, "design_report.json"), "w") as f:
        json.dump(report, f, indent=2)
    print(json.dumps(report, indent=2))
except Exception:
    traceback.print_exc()
    raise
